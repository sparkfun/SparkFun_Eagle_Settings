#usage "en: <b>Flip the entire design around X midpoint.</b> Very helpful for placing bottom silk correctly."
"<p>Usage: run sparkfun-flip</p>"
"<p>Author: <author>Nathan Seidle &lt;inathan@sparkfun.com&gt;</author><br />"
"Version: <em>1.0</em></p>"

//Original board dimension code came from https://gist.github.com/itavero/8042433

string bigScript = ""; //The big string of commands that we will eventually run as a script

real xMax = 0;
real yMax = 0;
real xMin = 0;
real yMin = 0;

void flip() {
	//Determine the current grid type and size
	int originalGridUnit; //1 = mm, 3 = inches
	board(B) {
		originalGridUnit = B.grid.unit;
	}
	
	//Turn on everything. Group everything.
    bigScript += "DISPLAY ALL; GROUP ALL;\n";

	//Change grid to inches
    bigScript += "GRID INCH ON;\n";
	
    //Mirror everything around the mid point of this design
    string s = "";
	sprintf(s, "MIRROR (>%.5f 0);\n", xMax/2);
    bigScript += s;
	
	//Return grid to original settings
	if(originalGridUnit == GRID_UNIT_MIC) //mic
	{
		bigScript += "GRID MIC ON;\n";
	}
	if(originalGridUnit == GRID_UNIT_MM) //mm
	{
		bigScript += "GRID MM ON;\n";
	}
	if(originalGridUnit == GRID_UNIT_MIL) //mil
	{
		bigScript += "GRID MIL ON;\n";
	}
	if(originalGridUnit == GRID_UNIT_INCH) //inch
	{
		bigScript += "GRID IN ON;\n";
	}

	//Turn on default layers
    bigScript += "DISPLAY NONE; DISPLAY 1 2 15 16 17 18 19 20 21 22 23 24 45 46 51; DISPLAY -25 -26 -27 -28;\n";

    //This clears the group selection
	bigScript += "GROUP;\n";
}

//Look at board dimensions and components
//Find the min/max coordinates of the design
void calculateDesignDimensions()
{
	//Find min/max dimensions of this board
    char firstPoint = 'y';
	char firstPointOverhang = 'y';
	
	board(B) {
        B.wires(W) {
            if (W.layer == LAYER_DIMENSION) {
                // Wire is on dimension layer
				real wx1 = u2inch(W.x1);
                real wy1 = u2inch(W.y1);
                real wx2 = u2inch(W.x2);
                real wy2 = u2inch(W.y2);
				
                // Start point of wire
                if (firstPoint == 'y') {
                    firstPoint = 'n';
                    xMax = wx1;
                    xMin = wx1;
                    yMax = wy1;
                    yMin = wy1;
                }
                else {
                    if (wx1 > xMax) {
                        xMax = wx1;
                    }
                    if (wx1 < xMin) {
                        xMin = wx1;
                    }
                    if (wy1 > yMax) {
                        yMax = wy1;
                    }
                    if (wy1 < yMin) {
                        yMin = wy1;
                    }
                }

                // End point of wire
                if (wx2 > xMax) {
                    xMax = wx2;
                }
                if (wx2 < xMin) {
                    xMin = wx2;
                }
                if (wy2 > yMax) {
                    yMax = wy2;
                }
                if (wy2 < yMin) {
                    yMin = wy2;
                }
            }
		}
	}
	
	//Check if this design has dimension lines. If it doesn't then it's probably a DXF import of an enclosure or something very weird.
	if(xMin == 0 && yMax == 0)
	{
		dlgMessageBox("!This board has no dimension lines. Cannot flip. Exiting.");
		exit(-1);
	}
}

if (board)
{
	calculateDesignDimensions(); //Find the max X of the design
	
	flip(); //Flip the design

	exit(bigScript); //Execute this generated script
}
else
{
    dlgMessageBox("Please run SparkFun Flip ULP from a board.");
    exit(1);
}
