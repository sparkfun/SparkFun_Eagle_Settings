#usage "en: <b>Outputs the contents of a design to Sparkle Friendly list</b> "
"<p>Usage: run SparkFun-BOM_Generator</p>"
	"<p>Author: <author>Owen Lyke, Nathan Seidle &lt;owen.lyke@sparkfun.com&gt;</author><br />"
	"Version: <em>1.0</em></p>"

/*

#usage "en: <b>Outputs the contents of a design to Sparkle Friendly list</b> PCBWay requires the user to create panels that are at least 75x75mm. If the panel is smaller than this they will reject it because their v-score machine can't handle it. This ULP takes a given design and replicates it until the panel is just over the dimensions specified by the user. It also adds dimension lines between copies and v-score text so that PCBWay knows where to v-score. This script will also detect overhanging parts and warn the user that gaps are needed. Script tries to identify the soldermask color based on the logos on the board (SparkFun vs SparkX vs LilyPad). Script looks for 0.8mm tag for thin boards. Script outputs a ordering_instructions.txt file containing all the characteristics of this panel."
"<p>Usage: run bom_sparkle</p>"
"<p>Author: <author>Nathan Seidle &lt;inathan@sparkfun.com&gt;</author><br />"
"Version: <em>1.0</em></p>"

*/

// Modified October 2021, Paul Clark
/*

Modification goals:
- Add Pick and Place Helper
  * Provide a 'quick' way to highlight particular parts when hand-populating a board

*/

// Modified October 2018, Owen Lyke
/*

Modification goals:
- improve detection of false positives (a part that is on the board but doesn't exactly match a production part that can be used)
	* previous method was to search the part name and make sure it included the value

- output a format that sparkle can handle to automatically set the quantity (this depends on SWIT adding this functionality in sparkle first)
	* currently in-progress, requires SWIT support but can be easily adapted into the output format when needed

- improve detetion of on-board vs no-package components
	* answered by allowing the user to flag entries as "BOM" or "Non-BOM" while still not missing any board elements
	* also looping through boad elements as opposed to schematic elements helps

*/

#include "z_Include_SF_BOM.ulp"

string pnpString = "";

if (schematic)
{
	exit("edit .brd; run " + ulpName);
}
if (board)
{

	int cnfrdres = configRead(configFile);
	if (cnfrdres)
	{
		configWrite(configFile);
	}

	// This loop does the initial categorization of all the components.
	// It is based off of only existence of PROD_ID or not
	initialGrouping();

	categorizeElements(); // Initial categorization

	dlgDialog("BOM Output"){

		dlgTabWidget{
			dlgTabPage("BOM View"){
				dlgHBoxLayout{

					dlgVBoxLayout{
						// BOM items
						dlgLabel("BOM Items");
	dlgListView(headerString, bomlistarry, bomSelected, bomSort);
	dlgPushButton("Move to Non-BOM")
	{
		if (bomSelected != -1)
		{
			master_status[bom_index_map[bomSelected]] = element_status_nonbom;
			categorizeElements();
		}
	}
}

dlgVBoxLayout
{
	// Non-BOM items
	dlgHBoxLayout
	{
		dlgLabel("Non-BOM Items");
	}
	// dlgStretch(1);
	dlgListView(headerString, nonbomlistarry, nonbomSelected, nonbomSort);
	dlgPushButton("Move to BOM")
	{
		if (nonbomSelected != -1)
		{
			master_status[nonbom_index_map[nonbomSelected]] = element_status_bom;
			categorizeElements();
		}
	}
}

// Filters
dlgVBoxLayout
{

	dlgLabel("Welcome to the BOM utility!");
	dlgPushButton("BOM Utility Help/Info/FAQ")
	{
		dlgDialog("NBOM Utility Info")
		{
			dlgLabel("This ULP lets you confidently keep track of all the elements on your board\n\
\n\
The main feature is the ability to change which items are considered to be part of the BOM.\n\
There are two ways of doins this:\n\
\t- 1) Manually move items from \"BOM Items\" to \"Non-BOM Items\" and back using the buttons below each list\n\
\t- 2) Apply a filter on the package names to exclude them from the \"Non-BOM Items\" list.\n\
\n\
* Notes: \n\
t- Items that have no PROD_ID, no contacts, and no holes are considered \"Non-Hardware\" and are excluded from BOM permanently\n\
\t- You can toggle the filter to see what is hidden from the \"Non-BOM Items\" list\n\
\t- Items in the \"BOM Items\" list are not affected by filters, so you can manually override a filter.\n\
\t- A defualt ilter file is loaded on startup, if present. You can also write your own filter files and load them.\n\
\t\t (each line of the text file is a filter entry)\n\
\t- The sparkle output will let you know how many BOM items are missing a PROD_ID (these are not displayed in the sparkle CSV)");
			// dlgListView("Qty\tPROD_ID\tPackage\tValue\tNames", silklistarry, silkSelected, silkSort);
			dlgPushButton("Close")
			{
				dlgAccept();
			}
		};
	}

	dlgPushButton("Export BOM as CSV: ")
	{
		// exportFilePath = dlgFileOpen("Select directory in which to export the BOM", EAGLE_HOME, "*");
		exportFilePath = dlgDirectory("Select directory in which to export the BOM", EAGLE_HOME);

		if (exportFilePath != "")
		{
			exportFilePath += "/bom_output.csv";

			output(exportFilePath, "wt")
			{
				string line = "Qty, PROD_ID, Names, Value, Package";
				printf("%s\n", line); // Header
				for (int indi = 0; indi < numUniqueEntries; indi++)
				{
					if (master_status[indi] == element_status_bom)
					{
						string local_names = replaceCharacter(master_names[indi], ',', ';');
						string local_values = replaceCharacter(master_values[indi], ',', ';');
						string local_prod_ids = replaceCharacter(master_prod_ids[indi], ',', ';');
						string local_package_names = replaceCharacter(master_package_names[indi], ',', ';');

						printf("%d, %s, %s, %s, %s\n", master_quantities[indi], local_prod_ids, local_names, local_values, local_package_names);
					}
				}
				dlgMessageBox("File created at: " + exportFilePath);
			}
			// dlgDialog("Rename Export File?")
			// {
			// 	dlgLabel("Output file created at: " + exportFilePath);
			// 	dlgLabel("Rename the file?");
			// 	dlgHBoxLayout{
			// 		dlgPushButton("-No"){
			// 			dlgAccept();
			// 		}
			// 		dlgPushButton("+Yes"){
			// 			string newExportFileName = "";
			// string data[];
			//    int line = fileread(data, exportFilePath);

			//    dlgDialog("Enter new name: "){
			//    	dlgTextEdit(&newExportFileName){ dlgAccept(); };
			//    }

			//    output(newExportFileName){
			//     if(line)
			//     {
			//     	int indi = 0;
			//     	while(data[indi] != ""){
			// 	    	filterStrings[indi] = data[indi];
			// 	    	indi++;
			// 	    }
			//   	}
			// }

			// 			dlgAccept();
			// 		}

			// 	}
			// };
		}
		else
		{
			dlgMessageBox("No path supplied");
		}

		exportFilePath = "";
	}

	dlgHBoxLayout
	{
		dlgVBoxLayout
		{
			dlgLabel("Filters status: \n(double click to change)");
			dlgListBox(filterStatus, filters_active) categorizeElements();
		}
		dlgVBoxLayout
		{
			dlgLabel("Number of filtered items \n(hidden from the Non-BOM list):");
			dlgTextView(numFilteredItems);
		}
	}
	dlgPushButton("View Non-Hardware Items")
	{
		dlgDialog("Non-Hardware Elements")
		{
			dlgLabel("Stuff");
			dlgListView(headerString, nonhardwarelistarry, nonhardwareSelected, nonhardwareSort);
			dlgHBoxLayout
			{
				dlgPushButton("Move to BOM")
				{
					if (nonhardwareSelected != -1)
					{
						master_status[nonhardware_index_map[nonhardwareSelected]] = element_status_bom;
						categorizeElements();
						dlgAccept();
					}
				}
				dlgPushButton("Move to Non-BOM")
				{
					if (nonhardwareSelected != -1)
					{
						master_status[nonhardware_index_map[nonhardwareSelected]] = element_status_nonbom;
						categorizeElements();
						dlgAccept();
					}
				}
			}
			dlgPushButton("Close")
			{
				dlgAccept();
			}
		};
	}
}
}
}

dlgTabPage("Filter Settings")
{
	// Filter Modification
	dlgLabel("Current Filter Strings \n(Apply only to items in the Non-BOM list - initially any item with a PROD_ID is displayed)");
	dlgListView("Filter", filterStrings, filter_string_selected, filter_string_sort);
	dlgPushButton("Remove from filter list")
	{
		removeFromFilterList();
		categorizeElements();
	}

	dlgLabel("Add new filters");
	dlgTextEdit(temp_filter_string);
	dlgPushButton("Add to filter list")
	{
		addToFilterList();
		categorizeElements();
	}

	dlgHBoxLayout
	{
		dlgPushButton("Load filter cnfg file")
		{
			customFilterFile = dlgFileOpen("Select a filter cnfiguration file (.flt)", path_ulp[0], "*.flt");
			configRead(customFilterFile);
			categorizeElements();
		}
		dlgPushButton("Save as default cnfg")
		{
			configWrite(configFile);
			categorizeElements();
		}
	}
}

dlgTabPage("Sparkle Output")
{
	dlgLabel("*Reminder* Don't forget to add a PCB part to the BOM in Sparkle");
	dlgLabel("CSV of PROD_IDs for Sparkle");
	dlgTextView(sparkleBOM);
	dlgLabel("PROD_ID Status:");
	dlgTextView(prod_id_warning);
}

dlgTabPage("Pick and Place Helper")
{
	dlgVBoxLayout{
		// BOM items
		dlgLabel("BOM Items");
		dlgListView(pnpHeaderString, pnplistarry, pnpSelected, bomSort);
		dlgPushButton("Show")
		{
			if (pnpSelected == -1)
			{
				pnpString = "";
			}
			else
			{
				pnpString = "show " + string(master_pnp_names[bom_index_map[pnpSelected]]);
			}
			dlgAccept();
		};
	};
}
}

dlgGridLayout
{

	dlgCell(0, 0)
	{
		dlgPushButton("Done")
		{
			setup_complete = 1;
			// result = 0;
			dlgAccept();
		};
	};
}
}
;
if (pnpString == "")
	exit(0);
else
	exit(pnpString);
}
else
{
	dlgMessageBox("Please run this ulp from the board editor");
	exit(1);
}
