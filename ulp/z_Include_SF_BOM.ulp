// string ulpName = "SparkFun-BOM_Generator";
string ulpName = argv[0];
int setup_complete = 0;
int redraw = 1;

// Master lists of properties that we care about
string master_prod_ids[];
string master_package_names[];
string master_values[];
string master_names[];
string master_pnp_names[];
int master_quantities[];
int master_status[];
int master_matches_filters[];
int numUniqueEntries = 0;

// There are four classifications that a given unique entry can have:
// - Valid for BOM, called "bom"
// - Invalid for BOM, called "nonbom"
// - Invlaid for BOM AND  hidden by filters, called "filtered"
// - Permanently removed from the search because it is a non-physical item, called "nonhardware"

// Status definitions
int element_status_unknown = 0;
int element_status_bom = 1;
int element_status_nonbom = 2;
// int element_status_filtered = 3;	// Filtered is not a status anymore, rather it is a show/hide flag and it is contained in master_matches_filters
int element_status_nonhardware = 4;

// Info for nonbom elements
string nonbomlistarry[];
int nonbomSort = 0;
int nonbomSelected = -1;
int nonbom_index_map[];

// Info for bom elements
string bomlistarry[];
string pnplistarry[];
int bomSort = 0;
int bomSelected = -1;
int pnpSelected = -1;
int bom_index_map[];

// Info for filtered elements
string filteredlistarry[];
int filteredSort = 0;
int filteredSelected = -1;
int filtered_index_map[];

// Info for nonhardware elements
string nonhardwarelistarry[];
int nonhardwareSort = 0;
int nonhardwareSelected = -1;
int nonhardware_index_map[];

// Counters for the number of elements in each category
int bomCount = 0;
int nonbomCount = 0;
int filteredCount = 0;
int nonhardwareCount = 0;

// Filter settings
string configFile = filesetext(argv[0], ".flt");
string filterStrings[] = {"fiducial", "stand-off"};
int filters_active = 1;
string filterStatus[] = {"off", "on"};
int filter_string_selected = -1;
int filter_string_sort = 0;
string temp_filter_string = "AddFilterHere";
string customFilterFile = "";

// GUI Vars
string prod_id_warning = "";
string headerString = "Qty\tPROD_ID\tNames\tValue\tPackage";
string pnpHeaderString = "Qty\tPROD_ID\tPart\tNames\tValue\tPackage";
string sparkleBOM; // A string for sparkle output
string numFilteredItems = "";
string exportFilePath = "";

// Function definitions

// Saves currrent filter strings to file "outfile"
void configWrite(string outfile)
{
	output(outfile)
	{
		int index = 0;
		while (filterStrings[index] != "")
		{
			printf("%s\n", filterStrings[index]);
			index++;
		}
	}
}

// Reads new filter strings from file "infile"
int configRead(string infile)
{
	if (filesize(infile))
	{ //Check if file exists

		int indk = 0;
		while (filterStrings[indk] != "")
		{ // Clear out old saved filter strings, if any exist
			filterStrings[indk] = "";
			indk++;
		}

		string data[];
		int line = fileread(data, infile);

		if (line)
		{
			int indi = 0;
			while (data[indi] != "")
			{
				filterStrings[indi] = data[indi];
				indi++;
			}
		}
		return 0;
	}
	else
	{
		return 1;
	}
}

void removeFromFilterList()
{
	if (filter_string_selected == -1)
	{
		return;
	}

	int indi = filter_string_selected;
	while (filterStrings[indi] != "")
	{
		filterStrings[indi] = filterStrings[indi + 1];
		indi++;
	}
}

void addToFilterList()
{
	if (temp_filter_string != "AddFilterHere")
	{
		int indi = 0;
		while (filterStrings[indi] != "")
		{
			indi++;
		}

		filterStrings[indi] = temp_filter_string;
		temp_filter_string = "AddFilterHere";
	}
}

//Strip off the alpha pre bits
//Remove leading zeros
string pidFormat(string id_str)
{
	string numeral_entries[];
	int numEntries = strsplit(numeral_entries, id_str, '-');
	if (numEntries < 2)
	{
		// dlgMessageBox("Too few entries found in the product id");
		return "NaN";
	}
	string numerals = numeral_entries[1];
	while (numerals[0] == '0')
	{
		string t = strsub(numerals, 1, strlen(numerals));
		numerals = t;
	}

	return numerals;
}

string replaceCharacter(string base, char from, char to)
{
	string retval = base;
	for (int indj = 0; indj < strlen(retval); indj++)
	{
		if (retval[indj] == from)
		{
			retval[indj] = to;
		}
	}
	return retval;
}

void generateSparkleList()
{
	int invalidPIDcount = 0;
	sparkleBOM = "";
	for (int indi = 0; indi < bomCount; indi++)
	{
		string temp = "";
		string prod_id = master_prod_ids[bom_index_map[indi]];
		string idNUM = pidFormat(prod_id);
		if (idNUM == "NaN")
		{
			invalidPIDcount++;
		}
		else if (indi < (bomCount - 1))
		{
			sprintf(temp, "%s,", idNUM);
		}
		else
		{
			sprintf(temp, "%s", idNUM);
		}

		//Print multiple of this PROD_ID to indicate the qty of the item
		for (int x = 0; x < master_quantities[bom_index_map[indi]]; x++)
		{
			sparkleBOM += temp;
		}
	}

	if (invalidPIDcount)
	{
		// string msg = "";
		// sprintf(msg, "Warning: %d items in BOM list without PROD_ID", invalidPIDcount);

		sprintf(prod_id_warning, "Warning: %d BOM items have no PROD_ID!", invalidPIDcount);
		// dlgMessageBox(msg);
	}
	else
	{
		sprintf(prod_id_warning, "All BOM items have PROD_ID. Good job :D");
	}
}

//Finds a string in a string no matter where, no matter capitalization
int containsString(string toSearch, string toFind)
{
	int pos = strstr(strlwr(toSearch), strlwr(toFind));
	if (pos >= 0) //String found
	{
		return (1);
	}
	return (0);
}

int filterMatch(string str)
{
	// Checks if str contains any of the filter strings
	int retval = 0; // Begin with no match
	int indi = 0;
	while (filterStrings[indi] != "")
	{
		if (containsString(str, filterStrings[indi]))
		{
			retval = 1;
		}
		indi++;
	}
	return retval;
}

int matchesFilters(UL_ELEMENT E)
{
	return filterMatch(E.package.name);
}

int getStatus(UL_ELEMENT E)
{
	// This is the function that contains rules that determine the status of a given element
	int this_status = element_status_unknown;

	// Flags for special circumstances
	int is_dnp = 0;
	int isALabel = 1;
	int has_pid = 0;

	// Test for DNP components
	if (containsString(E.attribute["Value"], "dnp") || containsString(E.value, "dnp"))
	// if((E.value == "DNP") || (E.attribute["Value"] == "DNP"))
	{
		is_dnp = 1;
	}

	// Test for pure-silkness
	//If this element has pads then it's not a label
	int padCount = 0;
	E.footprint.contacts(C)
	{
		padCount++;
	}
	if (padCount > 0)
		isALabel = 0;
	//If this element has a hole then it's not a label
	int holeCount = 0;
	E.footprint.holes(H)
	{
		holeCount++;
	}
	if (holeCount > 0)
		isALabel = 0;

	// See if it has a product id
	if (E.attribute["PROD_ID"])
	{
		has_pid = 1;
	}

	// Now take your info and make a decision about the status of the element:
	if (has_pid)
	{
		this_status = element_status_bom; // Has pid and IS hardware then its on the BOM
	}
	else if (is_dnp || isALabel)
	{
		this_status = element_status_nonhardware;
	}
	else
	{
		this_status = element_status_nonbom;
	}

	return this_status;
}

int elementsMatch(UL_ELEMENT E, int master_index)
{
	// The definition of a unique element is important, and we will define it in reverse.
	// A non-unique element is one that has a different:
	// - value
	// - package
	// - product id
	// - element_status

	int match = 1;
	if (E.value != master_values[master_index])
	{
		match = 0;
	}
	if (E.package.name != master_package_names[master_index])
	{
		match = 0;
	}
	if (E.attribute["PROD_ID"] != master_prod_ids[master_index])
	{
		match = 0;
	}
	if (getStatus(E) != master_status[master_index])
	{
		match = 0;
	}

	return match;
}

int elementIsUnique(UL_ELEMENT E)
{
	int is_unique = 1;
	for (int indi = 0; indi < numUniqueEntries; indi++)
	{
		if (elementsMatch(E, indi) == 1)
		{
			is_unique = 0;
		}
	}
	return is_unique;
}

int getMasterIndexMatch(UL_ELEMENT E)
{
	int index = 0;
	if (elementIsUnique(E) == 0)
	{
		while (elementsMatch(E, index) != 1)
		{
			index++;
		}
	}
	else
	{
		index = -1;
	}
	return index;
}

void initialGrouping()
{
	// This is how we initially count the number of unique elements, as well as fill out the arrays of data that can be used for sorting later

	board(B)
	{
		B.elements(E)
		{
			if (elementIsUnique(E))
			{
				// Add new unique item to the master arrays

				master_prod_ids[numUniqueEntries] = E.attribute["PROD_ID"];
				master_package_names[numUniqueEntries] = E.package.name;
				master_values[numUniqueEntries] = E.value;
				master_names[numUniqueEntries] = E.name;
				master_pnp_names[numUniqueEntries] = E.name;
				master_quantities[numUniqueEntries] = 1;
				master_status[numUniqueEntries] = getStatus(E); // Returns one of four categories, bom, nonbom, filtered, or nonhardware
				master_matches_filters[numUniqueEntries] = matchesFilters(E);
				numUniqueEntries++;
			}
			else
			{
				int index = getMasterIndexMatch(E);
				if (index != -1)
				{
					// Add quantity and additional name to that master item
					master_names[index] += (", " + E.name);
					master_pnp_names[index] += (" " + E.name);
					master_quantities[index]++;
				}
			}
		}
	}
}

void categorizeElements()
{
	// Clear out the old lists
	for (int indk = 0; indk < bomCount; indk++)
	{
		bomlistarry[indk] = "";
		pnplistarry[indk] = "";
		bom_index_map[indk] = -1;
	}
	for (int indj = 0; indj < nonbomCount; indj++)
	{
		nonbomlistarry[indj] = "";
		nonbom_index_map[indj] = -1;
	}
	for (int indl = 0; indl < filteredCount; indl++)
	{
		filteredlistarry[indl] = "";
		filtered_index_map[indl] = -1;
	}
	for (int indm = 0; indm < nonhardwareCount; indm++)
	{
		nonhardwarelistarry[indm] = "";
		nonhardware_index_map[indm] = -1;
	}

	// Reset the counters
	bomCount = 0;
	nonbomCount = 0;
	filteredCount = 0;
	nonhardwareCount = 0;

	// Recategorize the elements from the master lists
	for (int indi = 0; indi < numUniqueEntries; indi++)
	{
		string temp = "";
		sprintf(temp, "%d\t%s\t%s\t%s\t%s", master_quantities[indi], master_prod_ids[indi], master_names[indi], master_values[indi], master_package_names[indi]);
		string temp2 = "";
		sprintf(temp2, "%d\t%s\t%s\t%s\t%s\t%s", master_quantities[indi], master_prod_ids[indi], pidFormat(master_prod_ids[indi]), master_pnp_names[indi], master_values[indi], master_package_names[indi]);

		if (master_status[indi] == element_status_nonhardware)
		{
			nonhardwarelistarry[nonhardwareCount] = temp;
			nonhardware_index_map[nonhardwareCount] = indi;
			nonhardwareCount++;
		}
		else if (master_status[indi] == element_status_bom)
		{
			bomlistarry[bomCount] = temp;
			pnplistarry[bomCount] = temp2;
			bom_index_map[bomCount] = indi;
			bomCount++;
		}
		else if (master_status[indi] == element_status_nonbom) // Note: filters only apply to nonbom items, because in an ideal world a design would have no items that are both non-hardware and have no prod_id
		{
			if ((master_matches_filters[indi] == 1) && (filters_active == 1))
			{
				filteredlistarry[filteredCount] = temp;
				filtered_index_map[filteredCount] = indi;
				filteredCount++;
			}
			else
			{
				nonbomlistarry[nonbomCount] = temp;
				nonbom_index_map[nonbomCount] = indi;
				nonbomCount++;
			}
		}
		else
		{
			// Problems have arisen
		}
	}

	sprintf(numFilteredItems, "%d", filteredCount); // Show how many items are hidden

	generateSparkleList();
}
