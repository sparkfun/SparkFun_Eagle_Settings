/****************************************************************************************
*                                                                                       *
*                                                                                       *
****************************************************************************************/
board(B) 
{
  B.layers(L) printf("Layer %3d %s\n", L.number, L.name);
}

int i;
  
void set_defaults(void)
{

}
