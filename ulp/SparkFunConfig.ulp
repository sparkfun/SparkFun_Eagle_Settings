#usage  "en:<nobr><b>SparkFun EAGLE CAD Setup ULP</b>"
        "<p>"
        "<a href='https://raw.githubusercontent.com/sparkfun/SparkFun_Eagle_Settings/master/ulp/SparkFunConfig.ulp'>This ULP</a> sets up EAGLE to the default SparkFun\
          Electronics configuration.<br>"
        "All of the current SparkFun EAGLE files can also be installed."
        "<p>"
        "<author>Author: TechSupport@SparkFun.com</author>"

// THIS PROGRAM IS PROVIDED AS IS AND WITHOUT WARRANTY OF ANY KIND, EXPRESSED
// OR IMPLIED

// 1.2.2 - 2016-12-19 --- Removed old CAM job
// 1.2.1 - 2016-12-19 --- Updated number of libraries
// 1.2.0 - 2016-12-19 --- Updated list of libraries to match recent fixes to them
// 1.1.0 - 2016-03-22 --- Minor change, & decided all this made new minor versn 
// 1.0.3 - 2016-03-21 --- Fixed perm config by parsing & careful mod eagle.scr
// 1.0.2 - 2016-03-16 --- UI tweaks & permanent now appends to stock eagle.scr
// 1.0.1 - 2016-03-01 --- Added SparkFun logo
// 1.0.0 - 2016-02-15 --- Initial version

#require 6.0000
string Version = "1.2.2";

// Source configuration this section will need to be manually updated if the
// structure on GitHub changes
string settingsURLPath = "https://raw.githubusercontent.com/sparkfun/SparkFun_Eagle_Settings/master/";
string SFEagleFile = "eagle.scr";
string libraryDownloadPath = "https://raw.githubusercontent.com/sparkfun/SparkFun-Eagle-Libraries/master/";
string homeOfThisScript = "https://raw.githubusercontent.com/sparkfun/SparkFun_Eagle_Settings/master/ulp/SparkFunConfig.ulp";

// Default install paths can be modified for the session in the GUI
string localDRUDir = EAGLE_DIR + "/dru/";
string localCAMDir = EAGLE_DIR + "/cam/";
string localULPDir = EAGLE_DIR + "/ulp/";
string localSCRDir = EAGLE_DIR + "/scr/";
string localLBRDir = EAGLE_DIR + "/lbr/";

// These lists of libraries DRUs, etc must be manually updated if the structure
//   on GitHub changes. 
int numberOfLibraries = 31;
string libraries[] = {  "LilyPad-Wearables.lbr",
                        "SparkFun-Aesthetics.lbr",
                        "SparkFun-Batteries.lbr",
                        "SparkFun-Boards.lbr",
                        "SparkFun-Capacitors.lbr",
                        "SparkFun-Clocks.lbr",
                        "SparkFun-Coils.lbr",
                        "SparkFun-Connectors.lbr",
                        "SparkFun-DiscreteSemi.lbr",
                        "SparkFun-Displays.lbr",
                        "SparkFun-Electromechanical.lbr",
                        "SparkFun-Fuses.lbr",
                        "SparkFun-GPS.lbr",
                        "SparkFun-Hardware.lbr",
                        "SparkFun-IC-Amplifiers.lbr",
                        "SparkFun-IC-Comms.lbr",
                        "SparkFun-IC-Conversion.lbr",
                        "SparkFun-IC-Logic.lbr",
                        "SparkFun-IC-Memory.lbr",
                        "SparkFun-IC-Microcontroller.lbr",
                        "SparkFun-IC-Power.lbr",
                        "SparkFun-IC-Special-Function.lbr",
                        "SparkFun-Jumpers.lbr",
                        "SparkFun-LED.lbr",
                        "SparkFun-PowerSymbols.lbr",
                        "SparkFun-RF.lbr",
                        "SparkFun-Resistors.lbr",
                        "SparkFun-Retired.lbr",
                        "SparkFun-Sensors.lbr",
                        "SparkFun-Switches.lbr",
                        "User-Submitted.lbr"
};

int numberOfDRUs = 5;
string DRUs[] = { "SparkFun-2-layer-STANDARD.dru",
                  "SparkFun-2-layer-TIGHT.dru",
                  "SparkFun-2-layer-FAB-LIMIT.dru",
                  "SparkFun-4-layer-FAB-LIMIT.dru",
                  "SparkFun-4-layer-TIGHT.dru"
};

int numberOfULPs = 17;
string ULPs[] = { "Unrouted.ulp",
                  "bom_mod.ulp",
                  "exp-lbrs.ulp",
                  "adimv4_0mm.ulp",
                  "bom_sparkle.ulp",
                  "exp-project-lbr.ulp",
                  "autodim_in.ulp",
                  "drill-exactsize.ulp",
                  "import-bmp.ulp",
                  "autodim_mil.ulp",
                  "eagleUp_export.ulp",
                  "mirror-board.ulp",
                  "board_default.ulp",
                  "eagle_to_3d.ulp",
                  "oshw-logo.ulp",
                  "bom.ulp",
                  "eagle_to_3d_3_4.ulp"
};

int numberOfSCRs = 1;
string SCRs[] = { "eagle.scr"
};

int numberOfCAMs = 7;
string CAMs[] = { "GKO_ONLY.cam",
                  "STENCILcam-GTP_GBP_ONLY.cam",
                  "oshpark-gerb274x-4layer.cam",
                  "oshpark-gerb274x.cam",
                  "sfe-gerb274x-4layer.cam",
                  "sfe-gerb274x-withGBP.cam",
                  "sfe-gerb274x.cam"
};


////////////////////////////////////////////////////////////////////////////////
// A few globals (lazy)
////////////////////////////////////////////////////////////////////////////////
string run_info = "<b>Configure &amp; download libraries</b>";
int level = 0;      // Flag for configuration level
int permanent = 0;  // Flag for permanance of file writes
// Boolean, overwrite flags, and return value constants...
enum { FALSE = 0, TRUE, OFF, YES, NO, ABORT, YES_ALL, NO_ALL };
int writeAll = OFF; // File overwrite flag
int installLBRs = 1;
int installDRUs = 1;
int installULPs = 0;
int installSCRs = 1;
int installCAMs = 1;



////////////////////////////////////////////////////////////////////////////////
// Displays a dialog box with 5 options: Yes, No, Abort, No to All, & Yes to all
////////////////////////////////////////////////////////////////////////////////
int showLargeDialog(string title, string message)
{
  return dlgDialog(title)
  {
    dlgLabel(message);
    dlgHBoxLayout {
      dlgPushButton("+&Yes") dlgAccept(YES);
      dlgPushButton("&No") dlgAccept(NO);
      dlgPushButton("-&Abort") dlgReject(ABORT);
      dlgPushButton("N&o to All") dlgAccept(NO_ALL);
      dlgPushButton("Yes to &All") dlgAccept(YES_ALL);
    }
  };
}


////////////////////////////////////////////////////////////////////////////////
// Returns true if the file doesn't alreadt exist or use okay's the overwrite
////////////////////////////////////////////////////////////////////////////////
int okayToWrite(string fileName)
{
int returnValue = FALSE;  // Safe default
  if (filesize(fileName) > 0)
  {
    switch (writeAll)
    {
      case OFF:
        switch (showLargeDialog("Overwrite existing file?", fileName +
                " already exists.\n" +
                "This operation will overwrite it." +
                "\nAre you sure?"))
        {
          case YES:
            returnValue = TRUE; // Okay to write
            break;
          case NO:
            returnValue = FALSE;  // Don't overwrite file because user chose no
            break;
          case ABORT:
            exit(1);  // TODO: This might be extreme(?)
            break;
          case NO_ALL:
            returnValue = FALSE;  // Don't write this file
            writeAll = NO_ALL;    // Don't write any other remaining files
            break;
          case YES_ALL:
            returnValue = TRUE;   // Write this file
            writeAll = YES_ALL;   // Write any other remaining files
            break;
        }
        break;
      case YES_ALL:
        returnValue = TRUE; // Okay to write
        break;
      case NO_ALL:
        returnValue = FALSE;  // Don't overwrite file because user chose no
        break;
    }
  }
  else
  {
    returnValue = TRUE; // Okay to write the file since it doesn't exist
  }
  return returnValue;
}

////////////////////////////////////////////////////////////////////////////////
// Updates text on the GUI based on selected settings
////////////////////////////////////////////////////////////////////////////////
void updateMenu(void)
{
  // Update the dlgLabel 'run_info' with selected action(s)
  switch(level)
  {
    case 0 :  // Full configuration and download
      sprintf(run_info, "<b>Configure &amp; download libraries %s",
        (permanent == 1) ? "permanently</b>" : "</b>");
      break;
    case 1 :  // Configuration only
      sprintf(run_info, "<b>Configure %s",
        (permanent == 1) ? "permanently" : "");
      break;
    case 2 :  // Download only
      sprintf(run_info, "<b>Download libraries %s",
        (permanent == 1) ? "permanently</b>" : "</b>");
      break;
  }
  dlgRedisplay();
  return;
}

////////////////////////////////////////////////////////////////////////////////
// Download a file (text or binary) to local drive
////////////////////////////////////////////////////////////////////////////////
void downloadFile(string URLPath, string URLFile, string destination)
{
  sprintf(run_info, "<b>Downloading %s...</b>", URLFile);
  dlgRedisplay();
  
  if (okayToWrite(destination))
  {
    status("Downloading " + URLFile);

    char result[];
    int numberOfBytes = netget(result, URLPath + URLFile, 60 /*timeout (sec)*/);
    if (numberOfBytes >= 0)
    {
      fileerror();
      output(destination, (permanent) ? "wbF" : "wbDF")
      {
        for(int i = 0; i < numberOfBytes; ++i)
        {
          if (result[i] == 0)
          {
            printf("%c", 0x00);
          }
          else
          {
            printf("%c", result[i]);
          }
        }
      }
      if (fileerror())
      {
        exit(1);
      }
    }
    else
    {
      dlgMessageBox(neterror());
    }
  }
}


////////////////////////////////////////////////////////////////////////////////
// Download all of the SparkFun EAGLE libraries
////////////////////////////////////////////////////////////////////////////////
void downloadLBRs(void)
{
  for (int i = 0; i < numberOfLibraries; i++)
  {
    downloadFile(libraryDownloadPath, libraries[i], localLBRDir + libraries[i]);
  }
  writeAll = OFF;  // Turn off download all/none after getting all libraries
  return;
}

////////////////////////////////////////////////////////////////////////////////
// Download all of the SparkFun EAGLE DRUs
////////////////////////////////////////////////////////////////////////////////
void downloadDRUs(void)
{
  for (int i = 0; i < numberOfDRUs; i++)
  {
    downloadFile(settingsURLPath + "dru/", DRUs[i], localDRUDir + DRUs[i]);
  }
  writeAll = OFF;  // Turn off download all/none after getting all DRUs
  return;
}

////////////////////////////////////////////////////////////////////////////////
// Download all of the SparkFun EAGLE ULPs
////////////////////////////////////////////////////////////////////////////////
void downloadULPs(void)
{
  for (int i = 0; i < numberOfULPs; i++)
  {
    downloadFile(settingsURLPath + "ulp/", ULPs[i], localULPDir + ULPs[i]);
  }
  writeAll = OFF;  // Turn off download all/none after getting all ULPs
  return;
}

////////////////////////////////////////////////////////////////////////////////
// Download all of the SparkFun EAGLE SCRs
////////////////////////////////////////////////////////////////////////////////
void downloadSCRs(void)
{
  for (int i = 0; i < numberOfSCRs; i++)
  {
    downloadFile(settingsURLPath + "scr/", SCRs[i], localSCRDir + SCRs[i]);
  }
  writeAll = OFF;  // Turn off download all/none after getting all SCRs
  return;
}

////////////////////////////////////////////////////////////////////////////////
// Download all of the SparkFun EAGLE CAMs
////////////////////////////////////////////////////////////////////////////////
void downloadCAMs(void)
{
  for (int i = 0; i < numberOfCAMs; i++)
  {
    downloadFile(settingsURLPath + "cam/", CAMs[i], localCAMDir + CAMs[i]);
  }
  writeAll = OFF;  // Turn off download all/none after getting all CAMs
  return;
}

////////////////////////////////////////////////////////////////////////////////
// Appends EAGLE SCR to stock/existing eagle.scr to make it get called on launch
////////////////////////////////////////////////////////////////////////////////
void appendConfigurationScript(void)
{
  string lines[];
  string eagleScript = EAGLE_DIR + "/scr/eagle.scr";

  // Read existing eagle.scr to modify.
  int numberOfLines = fileread(lines, eagleScript);

  if (numberOfLines >= 0) // Make sure file was read
  {
    // Check to see if we've already modified this file, if so bail
    for(int i = 0; i < numberOfLines; ++i)
    {
      if (strrstr(lines[i],"SCRIPT "+localSCRDir+"configureLibraries.scr") >= 0)
      {
        dlgMessageBox("Looks like EAGLE is already configured to run\nthe " +
                      "SparkFun configuration");
        return;
      }
    }

    fileerror();
    output(eagleScript, (permanent) ? "wtF" : "wtDF")
    {
      for(int i = 0; i < numberOfLines; ++i)
      {
        // Insert call to to SFE script before SCH section AKA in the BRD sect
        // This simple look for first instance method seems to sufficeient do
        // to the way EAGLE parses scripts. They don't seem to allow multiple
        // sections of the same type. This relies on BRD being before SCH.
        if (strrstr(lines[i], "SCH:") >= 0)
        {
          printf("SCRIPT " + localSCRDir + "configureLibraries.scr;\n");
          printf(lines[i] + "\n");
        }
        // This assumption is a stretch. LBR currently follows SCH.
        else if (strrstr(lines[i], "LBR:") >= 0)
        {
          printf("SCRIPT " + localSCRDir + "configureLibraries.scr;\n");
          printf(lines[i] + "\n");
        }
        else  // Write anything else like normal
        {
          printf(lines[i] + "\n");
        }
      }
    }
    if (fileerror())
    {
      exit(1);
    }
  }
  else // File wasn't read or was empty.
  {
    dlgMessageBox("eagle.scr wasn't read configuration has failed.");
  }
}

////////////////////////////////////////////////////////////////////////////////
// Writes an EAGLE SCR to configure active libraries & run SparkFun's eagle.scr
////////////////////////////////////////////////////////////////////////////////
void writeConfigurationScript(void)
{
  output(localSCRDir + "configureLibraries.scr", (permanent) ? "wt" : "wtD")
  {
    // Check to see if a library exist for USE command. Checking a 'random' one
    // TODO: This can cause issues when downkoaded to custom path, but not
    // selected when configure is run.
    if (filesize(localLBRDir + libraries[2]) > 0)
    {
      printf("USE -*\n");

      for (int i = 0; i < numberOfLibraries; i++)
      {
        printf("USE " + localLBRDir + libraries[i] + "\n");
      }
    }

    // Always at least run our eagle.scr
    printf("SCRIPT " + localSCRDir + "SFEagle.scr\n");
  }
}

////////////////////////////////////////////////////////////////////////////////
// Create a configuration SCR and run it
////////////////////////////////////////////////////////////////////////////////
void configureSettings(void)
{
  writeAll = OFF; // Don't keep old setting from another download type
  // Keeping unique name to make sure the correct one is run
  string script = localSCRDir + "SFEagle.scr";
  status("Getting eagle.scr...");
  sprintf(run_info, "<b>Getting eagle.scr...</b>");
  dlgRedisplay();
  downloadFile(settingsURLPath + "scr/", SFEagleFile, script);
  status("Configuring EAGLE...");
  sprintf(run_info, "<b>Configuring EAGLE...</b>");
  writeConfigurationScript();
  if (permanent)
    appendConfigurationScript();
  script = localSCRDir + "configureLibraries.scr";
  exit("script '" + script + "'");
}

void warnAboutSpeed(void)
{
  dlgMessageBox("<b>Be patient while files download!</b><ul><li>This can take some time.</li><li>You will get a dialog box on error or</li><li>configuration tool will go away on success.</li><li>Current download is shown in status bar.</li></ul>");
}


////////////////////////////////////////////////////////////////////////////////
// Based on state of GUI run the desired tasks
////////////////////////////////////////////////////////////////////////////////
void doConfiguration(void)
{
  switch (level)
  {
    case 0 :  // Full configuration and download
      warnAboutSpeed();
      if (installLBRs)
        downloadLBRs();
      if (installDRUs)
        downloadDRUs();
      if (installULPs)
        downloadULPs();
      if (installSCRs)
        // TODO:Leave this out until we have more than eagle.scr downloadSCRs();
      if (installCAMs)
        downloadCAMs();
      configureSettings();
      break;
    case 1 :  // Configuration only
      configureSettings();
      break;
    case 2 :  // Download only
      warnAboutSpeed();
      if (installLBRs)
        downloadLBRs();
      if (installDRUs)
        downloadDRUs();
      if (installULPs)
        downloadULPs();
      if (installSCRs)
        // TODO:Leave this out until we have more than eagle.scr downloadSCRs();
      if (installCAMs)
        downloadCAMs();
      break;
  }
}



////////////////////////////////////////////////////////////////////////////////
// This function draws the main GUI
////////////////////////////////////////////////////////////////////////////////
void openDialog(void)
{
  dlgDialog("SparkFun EAGLE Configuration Tool")
  {
    dlgVBoxLayout
    {
      dlgHBoxLayout
      {
        dlgGroup("Configuration level")
        {
          dlgRadioButton("&Full configuration and download", level) //level= 0
          {
            updateMenu();
          }
          dlgRadioButton("&Configuration only", level)  // level = 1
          {
            updateMenu();
          }
          dlgRadioButton("&Download only", level) // level = 2
          {
            updateMenu();
          }
        }
        dlgGroup("Save downloads or remove them on EAGLE exit")
        {
          // Unchecked is 0, checked is 1
          dlgCheckBox("&Permanently write \\& edit files", permanent)
          {
            updateMenu();
          }
        }
        dlgLabel(
"<img src='data:image/png;base64,iVBORw0KGgoAAAANSUhEUgAAANgAAABkCAYAAADkKP7jAAAAGXRFWHRTb2Z0d2FyZQBBZG9iZSBJbWFnZVJlYWR5ccllPAAAAyhpVFh0WE1MOmNvbS5hZG9iZS54bXAAAAAAADw/eHBhY2tldCBiZWdpbj0i77u/IiBpZD0iVzVNME1wQ2VoaUh6cmVTek5UY3prYzlkIj8+IDx4OnhtcG1ldGEgeG1sbnM6eD0iYWRvYmU6bnM6bWV0YS8iIHg6eG1wdGs9IkFkb2JlIFhNUCBDb3JlIDUuNi1jMTExIDc5LjE1ODMyNSwgMjAxNS8wOS8xMC0wMToxMDoyMCAgICAgICAgIj4gPHJkZjpSREYgeG1sbnM6cmRmPSJodHRwOi8vd3d3LnczLm9yZy8xOTk5LzAyLzIyLXJkZi1zeW50YXgtbnMjIj4gPHJkZjpEZXNjcmlwdGlvbiByZGY6YWJvdXQ9IiIgeG1sbnM6eG1wPSJodHRwOi8vbnMuYWRvYmUuY29tL3hhcC8xLjAvIiB4bWxuczp4bXBNTT0iaHR0cDovL25zLmFkb2JlLmNvbS94YXAvMS4wL21tLyIgeG1sbnM6c3RSZWY9Imh0dHA6Ly9ucy5hZG9iZS5jb20veGFwLzEuMC9zVHlwZS9SZXNvdXJjZVJlZiMiIHhtcDpDcmVhdG9yVG9vbD0iQWRvYmUgUGhvdG9zaG9wIENDIDIwMTUgKE1hY2ludG9zaCkiIHhtcE1NOkluc3RhbmNlSUQ9InhtcC5paWQ6MTZFNzQ2MDNEODEwMTFFNUFBNkFEMkREODk1MzRBOEIiIHhtcE1NOkRvY3VtZW50SUQ9InhtcC5kaWQ6MTZFNzQ2MDREODEwMTFFNUFBNkFEMkREODk1MzRBOEIiPiA8eG1wTU06RGVyaXZlZEZyb20gc3RSZWY6aW5zdGFuY2VJRD0ieG1wLmlpZDoxNkU3NDYwMUQ4MTAxMUU1QUE2QUQyREQ4OTUzNEE4QiIgc3RSZWY6ZG9jdW1lbnRJRD0ieG1wLmRpZDoxNkU3NDYwMkQ4MTAxMUU1QUE2QUQyREQ4OTUzNEE4QiIvPiA8L3JkZjpEZXNjcmlwdGlvbj4gPC9yZGY6UkRGPiA8L3g6eG1wbWV0YT4gPD94cGFja2V0IGVuZD0iciI/PpdEP6QAAA7HSURBVHja7F0LtFVFGZ4bKogmPhBFUFFAkETRNFPzgWlqQmJKvvWKgK8y1HwkWuRyZZpotFQerusjlTItyScWPrBAxcCQ1AxQEE1QfKF4AcHb93X+u9b2tGef2efsc+65537fWv/a5+w9e2bvmfn2/PPPPzN1TU1NThCE8uBLygJBEMEEQQQTBEEEEwQRTBBEMEEQRDBBEMEEoQaxXhaR1NXVKSdrBG/v0XsQDiMh+0M2hTRCZkMegDR0nTP//baWJ6U4Y9Rl4ckhgtUEsbrgcAfk8IRgH0F+DJkAojWJYBVqwYSaINdMSE9PkGcgo+24vtWbz5RzIpgQhkkJ5JoFOQgt1hr7v0rZFQ4ZOdR67YjDUQlBro+QSxDBhJToX+D6xsoiEUwoHo0Fro9CK9c+puXbDDJA2SeCCcmY4ZINFrtA7gWZNsg73wkyG+cvUhaKYIIH6F+txOH2AsEGQ2aBTHtFzh1g9edanD9DORkPjYMJVPe64TAXskVA8DmQdyEHu5zJniBJ+4Gsb9Ri/pTCEbVgAluxt3A4BfJ5QPA9IIdFyEVsBBmjnFQLJiS3ZCfh8JsiP7yryVWQ9QO1YGrB2jqR2kN6QDbJa8nuxqG+yGhpaRyk3BXB2jKxBkOexM9PIa9DFuD/d/NIdicOtxaZxAHK5S9CrlJtg1jU4W+GnBU5/SrkQBBqWcwt4yHDikiqn3JbLVhbxJl55CIaPOQiVhSZzlbKahGsrbVeLOPLYy71TbjtO9KIRDAhDLtBusWcrwf5Rpj6GCXkUByuLDKtD5Xd+uK0Neyc8HHlNJULQarncaQt+muQPiWktVjZLYK1NXQpcL1PiaSK4jllt1REoXx4UFkgggnlwbyuc+bPUzaIYEJ5cI2yQAQTygOu2/FbZYMIJmQPLoIzHOrh58oKEUzIHiPV9xLBhPLgEnMOFjzQOJhQDLiM29kg163KChFMyBbPQs4EuV5UVohgQjbgbOXHITdBHm1L69KLYEJW4PywhyEf239aBblWx0LILJDqU2WRCCakB9dE/KFrYzumiGBCJcBVfY8Csf6irCgPZKZvu6AKeLzIJYIJ5QG9Lx5QNohgQva4FOS6TdkgggkB6Ll9jzTleAPIdU2J6W0CUf89AMqk1k8uLlDDfZP3CQjOhUUvLCINLiXAlam47uEOkHZ2no6+by5cvKi3SkIEqzVisdJfB9nf5TYnL4TpkGFpTPFIoyMOt0BO9ATpANlSpSGC1RKxuJfyzyHfS3EbB5GHFLEV7GSXvL2sIILVFLm+hcND7os7mxTCe5DBINeHKdM6XOQSwdoatklJLlfCdJKzE669Dfm39cVkKBPBhCKwn+f8VMighYsXrVMWFYa+PkKcesj9mH27XU4WuUQwoTR0LKAeCi2pIuILyM3YjoQcCtkV0guysRXcJy63hjl1eE7eexhfxJkp4t4Qh69A1uG+F+wcx2FGQg6JpMUdQrgH1jOQexD2qSLeg2M+3ACc4z9c/XZbl9sudT2LnwYE7kvMpaenUUK/7mYC3wWyFvfMiZyn+X2Ey+2B3N3lHHIPQZi/l1AefHbfOBnN9vci/k8RrhN+H12AYIcgXPfI/5dx7yyc4/NuFxN+Aa7/rcDzfcPKLR9Lce/USLhjrWzzcR/CfWJh+uNwhtWFHSEbWn17w+rb3Qj7dKUIlukWsuZR8H2XG/jcOkUUXHL54rgXR5zcBWSoEbWZrExnnMsNmv4Ucpl1uJMwgyREGi8HVEgS+CqXs6Kl2R+X86cuRxq3x8TJNeKPg/Q36WVxj0P4Ubj+ZZfbl+ukmHgH8gOBMPX4Hefi9BGub+p5F5KYm+519jzzObh3vJHrzy63Pn0aND//FBdvdbwD1+sL5Dfz67SYS9Nx70GRcItw2D4mHD+ESyE3uNyAeKEy47y3kxF3kGW1KraQxcuzgt9jFX/rlLfvzUqAOM6KuUZzMXf74Ndrp7xn5gzbKwLI1dxpfx5pHFrgPVjB2aIMSUkugruY3IY4xsVcO8w+BtxRsnc0bqvcT3rIVUqZ9DKjRBy56E0/zMjFweLHiyBXtYCt1CMutwdaSJlRu3oM771+uR8syz7YaCNBKc9ys6kaIRhiX6u0fYs/IY3dPRXyCJfbBHyDEvPiPMR1dIrwXDzmqxmTi+rsUy5+6yKS61SQ6zYj1xNZp19hsOUamPIefkzObxV9MBQS9eKLPZfZrE+EcJEUzp7lbh9076Ha0D5f24SMhewekGy+qsC4X7PK08O+ar6v3WQ8826oYGvyLGcTEz46fyA5IUusH0C15PSEZz0Pcn/AexwIGZAxubpbixhHLuZTPd59svUDSW6qp4vzPnbbeqLnrpirIv/frwKCHVbkffxAX9sajBwDrfOfD3bQ90FhLs07fzcKl32Jp2NaiwFW+ecGpr3a+nyTcM/KiJHlZMj1kE1i7mG/jnsQT4icG5RQqc5G3BNiKvIEq8hxY0ZfD3x+H7mW0wDi/OZyH7nYInESZU8PuY7Fu/xvHhgNG2bEyY+D/bkPPEkcX4zBqEKYaoSZbXWPqvgoMxrFYUe8a7+QfnlLq4i+/aWWxZDLWeHSsDHFc9++KdIeirhuaCaXxb0a0mBWzDUJLUwUPtV0vrVsce/ACtvgua+DGS7S4HlTszsi7i0hXa3FnRFIrs6m7vUtRK4aBNfG/zbe70nICpYNiQMZaWq/D/1bQwvW3nO+Bwr9OLzkPZ7rY1z8pgH/Cs1UxO3dk8rMx1ebcSEfO9NaiDAv2f+lpgLm468Ik2RGSlKR2qXIw99BTkFaa/PegWb/dQHk6mTWsV08msRgxPV4jZKL3YILEsqJ899O9Vzr1RoItiSp4qDwaYKlZ/a0aIuG36/g8EoJ6d4YEIam7ys8rTVbypfsWa4qoq9DK9QpGeXfsHxypSzHx1y8FZDkomvTE652MdOnKVnZvoyy4odwc4/hq+oJ9oipYj7r2xEmrJRsnZ41oerzUoEWwocVFkciEPcypEmdfC+PJemWFITawPppfayPdUJGX0COJTWWcD/7v3sn5NNcV9sIeb83PQTbqOoJhsqxHJWPatjVAcH7mtTb///gXlroJkbUtRC8ivChW+b800OwbRPIxGf8psuZr0koWi3pzV5XhnIoZ79oK8ivXcZjbFWG5QFhPmyJB8tsHAyV/Rc4nANZmfJWVtofkAS0LKYwDLybIo1lnvObxhBrMGSOqa5UQU83VbJbmchFk/fCMpfziXinITVMsBDyNLVqghnJxpvK9DOXm0WbFmzVpgeSLI1Ht69v0yFCrDpIg7UmuwfGS1/E+0vMtndTtMSlYALebwsntF6CGcnooDkG0tfUquEuZyadHxgFK/dPAsJ1TvFYvooVtQBe4HJjY0mt4O9dziJJn0L6RXYx9asUZEkurs0xpYCqWI2oq1WClXXCJUhGD+YGk+ZBUI66c6yHA7vtElqyiwpE3yfFo/ROUjPxXGzJRicQix+Jh+OMMZXwZ0vRD+FY3iIIB067e1RFes5PqeBzheRPV7Vg2RCO6tBdEPYHdkto1TobGZOwuc+nMI8AHZx/4PoFO9ICt5knDMfxHkqwdFaD2kUL7sF4xnkQ7o4yKiHsePPUqBS2CwjTTwRLrsRrIU0x0jGBbLQYJjlbhphPQ5x9aUr3PcczdtzJ13nGc04vEH/fKijHRpIrkre0yj7iCcuZDr+qoKFhD/vI+eoOrbvdRLBkvO45X8gJ8zPP+Sbnt/xFMTzJ+x7XWHC+oYN3IM0TPX2qarukVXNtXOzUKi1bzsvzja2dhmc/MuP0FnvO8+M2MiH/fllNmUYDG2dCcHInZPNqIZjPBWeczTb2qW6Xee57MXDglcTg9JMR0a+kWQS5xNnT1rmPwyTzJSR8XgC0Zg71PD/zjmb8HaqRXXg3fvSSvFMmZawqJo1hXoe0zodsZnm3HoSzxOmUfGAVkYtdDjpv04DVw+XmjB1QDUaOiR51jQO5L5r5m5m5xPo6u1p4n6EizcYEnDoyCTIW6bxirWJPlzzpk8aNsZH/M63VjLNm3Yl497HnZ6vKry494Ee4wtNMWnrNE678y1kFO8dc28ZUxfqM0nrM+b15aOjgzIbrkZcf24erGkEr62j78C+z/zdafW25FszWxhjrucyW5VyXMx/TZWmaZbaPXJw3NiEgWU61WJ3X2tD1ab8C5CKRhkWni+M31cWpnvCsHNwBkgt+0tud7l03ubA5XF1auBVjhT8nIUhmqiLS4hDBHwOCxpHruSohGLURjt+yZecQ0z9c/HSniquIxCWQ20uMgy93JKebBIRlK0QvizTjSCTXubQKxlzj9JUPinjmac4/JWa7lq4xNnfrrgqpij+yvm0aPFhF/bC3jGRUE5st3I1VQTBOq4Cwwp+U0OH1YZWpK3sijjdTpMmpLkNcmNsUx+QON2+TuLgWWH8g1B+SLmEcdD4i4Z59q6TicHEgn5WvWVXMog6wgg50YV48/DByqv8xLp1XTjlBZ4NrjVz8cDbYuRbvg0UzmVPR6fFwkMvNlqUZluMcnSLB1tpL0An3UcgDuO+9ItN70Awpw62wqLo1LxfAFoke9/e53NyxxgJxzbOOLg0bJ5jK2azmrTMiz7Vn5vJfy61zfKmLH8t5K/Kb5v64YYkVKV53lieO1QXe6x1bI2RAQgd/o8ik1UbnH0JZUCAtTg1hn+VEK48981T2haaOj2927kb4eZ708j+2V3pUtukBeXeji/dyeSHy7DPoi+pyThDsSx6Dc0tK4UOmy7YFWGmoijQGqoDN94yyL10+FiOeHp57WAhrcH1VBpYlWipZ+VY4odg8ZD+W45orI5bbVoNSOFLRtelD16HLIJ0VGca1LmUrI/x/Hn7mWmi6SEtDS2cLgggmCCKYIAgimCCIYIIgglUIXIXqcxWVIIKVAbY/FLfFaVRxCSJYeUhG30G64CxXkQkiWHlIRo9r+va9pmITRLDykIz+i5ybNVtFJ4hg5SEZp0PQ6/1RFZ9Q7cjE2VcQhBppwQRBBBMEQQQTBBFMEEQwQRBEMEEQwQRBBBMEIQD/FWAAvmKfJgh/8BAAAAAASUVORK5CYII='>"
        );
      }
/*
      dlgGroup("Library source URL")
      {
        dlgStringEdit(libraryDownloadPath);
      }
*/
      dlgGroup("Directory libraries will be written to")
      {
        dlgHBoxLayout
        {
          dlgCheckBox("", installLBRs);
          dlgLabel(localLBRDir, 1);
          dlgStretch(1);
          dlgPushButton("&Change")
          {
            string temporaryPath =
              dlgDirectory("Select destination directory",
              localLBRDir);
            if (temporaryPath)  // Cancel button returns empty string
            {
              localLBRDir = temporaryPath + "/";
            }
          }
        }
      }
      dlgGroup("Directory design rules will be written to")
      {
        dlgHBoxLayout
        {
          dlgCheckBox("", installDRUs);
          dlgLabel(localDRUDir, 1);
          dlgStretch(1);
          dlgPushButton("&Change")
          {
            string temporaryPath =
              dlgDirectory("Select destination directory",
              localDRUDir);
            if (temporaryPath)  // Cancel button returns empty string
            {
              localDRUDir = temporaryPath + "/";
            }
          }
        }
      }
      dlgGroup("Directory User Language Programs will be written to")
      {
        dlgHBoxLayout
        {
          dlgCheckBox("", installULPs);
          dlgLabel(localULPDir, 1);
          dlgStretch(1);
          dlgPushButton("&Change")
          {
            string temporaryPath =
              dlgDirectory("Select destination directory",
              localULPDir);
            if (temporaryPath)  // Cancel button returns empty string
            {
              localULPDir = temporaryPath + "/";
            }
          }
        }
      }
      dlgGroup("Directory scripts will be written to")
      {
        dlgHBoxLayout
        {
          dlgCheckBox("", installSCRs);
          dlgLabel(localSCRDir, 1);
          dlgStretch(1);
          dlgPushButton("&Change")
          {
            string temporaryPath =
              dlgDirectory("Select destination directory",
              localSCRDir);
            if (temporaryPath)  // Cancel button returns empty string
            {
              localSCRDir = temporaryPath + "/";
            }
          }
        }
      }
      dlgGroup("Directory CAM jobs will be written to")
      {
        dlgHBoxLayout
        {
          dlgCheckBox("", installCAMs);
          dlgLabel(localCAMDir, 1);
          dlgStretch(1);
          dlgPushButton("&Change")
          {
            string temporaryPath =
              dlgDirectory("Select destination directory",
              localCAMDir);
            if (temporaryPath)  // Cancel button returns empty string
            {
              localCAMDir = temporaryPath + "/";
            }
          }
        }
      }
    }
    dlgStretch(1);
    dlgLabel(run_info, 1);
    dlgHBoxLayout
    {
      dlgPushButton("+OK")
      {
        doConfiguration();
        dlgRedisplay();
        dlgReject();
      }
      dlgLabel(" ULP-Version " + Version);
      dlgPushButton("-Cancel") exit(0);
    }
  };
}


////////////////////////////////////////////////////////////////////////////////
// Compares the version of this ULP with the latest found on GitHub. If there
// is a newer version this ULP replaces itself with the newer one and runs it.
////////////////////////////////////////////////////////////////////////////////
void updateULP(void)
{
  string latestULP;
  int numberOfBytes = netget(latestULP, homeOfThisScript);
  if (numberOfBytes >= 0)
  {
    if (numberOfBytes == 0) return; // No network error, but garbage

    // Process latestULP to find version definition
    int firstChar = strstr(latestULP, "string Version = ");
    string integer;
    // Update firstChar index to be first character index in the version string
    firstChar = strstr(latestULP, "\"", firstChar) + 1;
    int lastChar = strstr(latestULP, "\"", firstChar);
    string latestVersion = strsub(latestULP, firstChar, lastChar - firstChar);

    string current[], latest[];
    if (strsplit(latest, latestVersion, '.') != 3)
    {
      dlgMessageBox("Latest version of this ULP not found.");
    }
    if (strsplit(current, Version, '.') != 3)
    {
      dlgMessageBox("Version of this not ULP not valid.");
    }

    // Compare version numbers to see if this file is current
    for (int i = 0; i < 3; i++)
    {
      if (latest[i] > current[i])
      {
        dlgMessageBox("ULP isn't current, saving newer version...");
        output(argv[0], "wbF")
        {
          printf("%s", latestULP);
        }
        if (fileerror())
        {
          exit(1);
        }
        exit("RUN '" + argv[0] + "'");  // Run latest version
      }
    } // End of for loop
  }   // End successful network read
  else
  {
    dlgMessageBox(neterror());
  }
}

//dlgMessageBox(usage, "OK");

void main(void)
{
  if (library)  // The USE command isn't valid in lbr view, so config fails
  {
    dlgMessageBox("Only run this ULP in a schematic or board");
    exit(-1);
  }
  updateULP();
  openDialog();
}
